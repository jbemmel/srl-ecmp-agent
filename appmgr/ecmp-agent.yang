module ecmp_agent {

    yang-version "1";

    // namespace
    namespace "urn:srl_test/ecmp-agent";

    prefix "ecmp_agent";

    // import srl_nokia-common {
    //    prefix srl_nokia-comm;
    // }

    revision "2021-05-12" {
        description "Initial revision";
        reference "TBD";
    }

    grouping ecmp-agent-top {
        description "Top level grouping for ECMP agent sample app";

        container ecmp-agent {
            presence "presence container";
            description "Top level enclosing container for auto config agent sample app
                         config and operational state data";

            leaf network-instance {
                description "Network instance in which to execute traceroute";
                type string;
                default "default";
            }

            list ecmp-result {
                key name;
                config false;

                leaf name {
                  type string; // TODO timestamp
                }
                leaf output {
                  type string;
                  description "Last output from traceroute";
                }
            }

            leaf path-count {
                type uint64;
                config false;
            }
         }
    }

    // data definition statements
    uses ecmp-agent-top;
}
